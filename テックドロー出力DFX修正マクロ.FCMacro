# -*- coding: utf-8 -*-

import os
import re
import math
from PySide import QtWidgets


LINE_TOL = 0.00001


app = QtWidgets.QApplication.instance()

if app is None:
    app = QtWidgets.QApplication([])


QtWidgets.QMessageBox.information(
    None,
    "DXF修正",
    "修正するデータを選択してください"
)


file_path, _ = QtWidgets.QFileDialog.getOpenFileName(
    None,
    "TechDrawで出力したDXFを選択",
    "",
    "DXF Files (*.dxf);;All Files (*)"
)

if not file_path:
    raise SystemExit


base, ext = os.path.splitext(file_path)
output_path = base + "_修正済み.dxf"


def read_dxf_text(path):

    with open(path, "rb") as f:
        data = f.read()

    if data.startswith(b"\xef\xbb\xbf"):
        try:
            return data.decode("utf-8-sig")
        except Exception:
            pass

    try:
        return data.decode("utf-8")
    except Exception:
        pass

    try:
        return data.decode("cp932")
    except Exception:
        pass

    return data.decode("latin-1")


text = read_dxf_text(file_path)

text = text.replace("\r\n", "\n")
text = text.replace("\r", "\n")

lines = text.split("\n")


ENTITY_TYPES = {
    "LINE",
    "LWPOLYLINE",
    "POLYLINE",
    "CIRCLE",
    "ARC",
    "ELLIPSE",
    "TEXT",
    "MTEXT",
    "DIMENSION",
    "LEADER",
    "INSERT",
    "POINT",
    "SOLID",
    "3DFACE"
}


def get_group_values(entity_lines, code):

    values = []

    i = 0

    while i + 1 < len(entity_lines):

        if entity_lines[i].strip() == str(code):
            values.append(
                entity_lines[i + 1].strip()
            )

        i += 2

    return values


def get_group_value(entity_lines, code, default=None):

    values = get_group_values(
        entity_lines,
        code
    )

    if values:
        return values[0]

    return default


def get_layer(entity_lines):

    return get_group_value(
        entity_lines,
        8,
        ""
    )


def change_layer(entity_lines, new_layer):

    result = list(entity_lines)

    i = 0

    while i + 1 < len(result):

        if result[i].strip() == "8":

            result[i + 1] = new_layer

            return result

        i += 2

    return result


def get_section_range(data, section_name):

    start = None
    end = None

    i = 0

    while i < len(data) - 1:

        if (
            data[i].strip() == "0"
            and
            data[i + 1].strip() == "SECTION"
        ):

            j = i + 2

            found = False

            while j < len(data) - 1:

                if (
                    data[j].strip() == "2"
                    and
                    data[j + 1].strip() == section_name
                ):

                    found = True
                    break

                if (
                    data[j].strip() == "0"
                    and
                    data[j + 1].strip() == "ENDSEC"
                ):

                    break

                j += 1

            if found:

                start = i

                k = j + 2

                while k < len(data) - 1:

                    if (
                        data[k].strip() == "0"
                        and
                        data[k + 1].strip() == "ENDSEC"
                    ):

                        end = k + 2
                        return start, end

                    k += 1

        i += 1

    return None, None


def parse_entities(data, start, end):

    result = []

    i = start

    while i < end:

        if (
            i + 1 < end
            and
            data[i].strip() == "0"
        ):

            typ = data[i + 1].strip()

            if typ in ENTITY_TYPES:

                entity_start = i

                j = i + 2

                while j < end:

                    if data[j].strip() == "0":
                        break

                    j += 1

                result.append({
                    "type": typ,
                    "start": entity_start,
                    "end": j,
                    "lines": data[
                        entity_start:j
                    ]
                })

                i = j
                continue

        i += 1

    return result


entities_start, entities_end = get_section_range(
    lines,
    "ENTITIES"
)


if (
    entities_start is None
    or
    entities_end is None
):

    QtWidgets.QMessageBox.critical(
        None,
        "DXFエラー",
        "ENTITIES SECTIONが見つかりません。"
    )

    raise SystemExit


entities = parse_entities(
    lines,
    entities_start,
    entities_end - 2
)


for ent in entities:

    old_layer = get_layer(
        ent["lines"]
    )

    new_layer = None

    if (
        old_layer.startswith("*")
        and
        "dimension" in old_layer.lower()
    ):

        new_layer = "寸法"

    elif old_layer.lower().startswith(
        "dimension"
    ):

        new_layer = "寸法"

    elif old_layer.lower().startswith(
        "annotation"
    ):

        new_layer = "注釈"

    elif old_layer == "ProjItem001":

        new_layer = "側面図2"

    elif old_layer == "ProjItem":

        new_layer = "側面図"

    elif old_layer == "View":

        new_layer = "正面図"

    if new_layer is not None:

        lines[
            ent["start"]:
            ent["end"]
        ] = change_layer(
            ent["lines"],
            new_layer
        )


entities = parse_entities(
    lines,
    entities_start,
    entities_end - 2
)


for ent in entities:

    if ent["type"] != "LWPOLYLINE":
        continue

    lines[
        ent["start"]:
        ent["end"]
    ] = change_layer(
        ent["lines"],
        "L"
    )


entities = parse_entities(
    lines,
    entities_start,
    entities_end - 2
)


for ent in entities:

    if ent["type"] != "DIMENSION":
        continue

    lines[
        ent["start"]:
        ent["end"]
    ] = change_layer(
        ent["lines"],
        "寸法"
    )


entities = parse_entities(
    lines,
    entities_start,
    entities_end - 2
)


def get_line_points(entity_lines):

    x1 = get_group_value(
        entity_lines,
        10
    )

    y1 = get_group_value(
        entity_lines,
        20
    )

    x2 = get_group_value(
        entity_lines,
        11
    )

    y2 = get_group_value(
        entity_lines,
        21
    )

    if None in (x1, y1, x2, y2):
        return None

    try:

        return (
            float(x1),
            float(y1),
            float(x2),
            float(y2)
        )

    except Exception:

        return None


def dist(x1, y1, x2, y2):

    return math.hypot(
        x2 - x1,
        y2 - y1
    )


def same_point(a, b):

    return (
        abs(a[0] - b[0]) <= LINE_TOL
        and
        abs(a[1] - b[1]) <= LINE_TOL
    )


def same_line(a, b):

    if (
        same_point(
            (a[0], a[1]),
            (b[0], b[1])
        )
        and
        same_point(
            (a[2], a[3]),
            (b[2], b[3])
        )
    ):

        return True

    if (
        same_point(
            (a[0], a[1]),
            (b[2], b[3])
        )
        and
        same_point(
            (a[2], a[3]),
            (b[0], b[1])
        )
    ):

        return True

    return False


def point_on_segment(
    px,
    py,
    ax,
    ay,
    bx,
    by
):

    abx = bx - ax
    aby = by - ay

    apx = px - ax
    apy = py - ay

    length2 = (
        abx * abx
        +
        aby * aby
    )

    if length2 <= LINE_TOL * LINE_TOL:

        return (
            dist(
                px,
                py,
                ax,
                ay
            )
            <= LINE_TOL
        )

    cross = abs(
        abx * apy
        -
        aby * apx
    )

    if cross > (
        LINE_TOL *
        math.sqrt(length2)
    ):

        return False

    dot = (
        apx * abx
        +
        apy * aby
    )

    if dot < -LINE_TOL:
        return False

    if dot > length2 + LINE_TOL:
        return False

    return True


def segment_inside(short_line, long_line):

    return (
        point_on_segment(
            short_line[0],
            short_line[1],
            long_line[0],
            long_line[1],
            long_line[2],
            long_line[3]
        )
        and
        point_on_segment(
            short_line[2],
            short_line[3],
            long_line[0],
            long_line[1],
            long_line[2],
            long_line[3]
        )
    )


line_entities = []


for ent in entities:

    if ent["type"] != "LINE":
        continue

    pts = get_line_points(
        ent["lines"]
    )

    if pts is None:
        continue

    length = dist(
        pts[0],
        pts[1],
        pts[2],
        pts[3]
    )

    line_entities.append({
        "entity": ent,
        "points": pts,
        "length": length,
        "remove": False
    })


for i in range(
    len(line_entities)
):

    if line_entities[i]["remove"]:
        continue

    a = line_entities[i]["points"]

    for j in range(
        i + 1,
        len(line_entities)
    ):

        if line_entities[j]["remove"]:
            continue

        b = line_entities[j]["points"]

        if same_line(a, b):

            line_entities[j]["remove"] = True


sorted_lines = sorted(
    line_entities,
    key=lambda x: x["length"],
    reverse=True
)


for i in range(
    len(sorted_lines)
):

    long_item = sorted_lines[i]

    if long_item["remove"]:
        continue

    long_line = long_item["points"]

    for j in range(
        i + 1,
        len(sorted_lines)
    ):

        short_item = sorted_lines[j]

        if short_item["remove"]:
            continue

        if (
            long_item["length"]
            -
            short_item["length"]
            <= LINE_TOL
        ):

            continue

        if segment_inside(
            short_item["points"],
            long_line
        ):

            short_item["remove"] = True


remove_ranges = []


for item in line_entities:

    if item["remove"]:

        ent = item["entity"]

        remove_ranges.append(
            (
                ent["start"],
                ent["end"]
            )
        )


for start, end in sorted(
    remove_ranges,
    reverse=True
):

    del lines[
        start:end
    ]


result_text = "\n".join(lines)


if not result_text.endswith("\n"):
    result_text += "\n"


result_text = re.sub(
    r"(\$DWGCODEPAGE\s+3\s+)[^\s]+",
    r"\1ANSI_932",
    result_text,
    flags=re.IGNORECASE
)


result_text = re.sub(
    r"(^\s*3\s*\n)"
    r"(\s*arial\.ttf\s*\n)",
    r"\1msgothic.ttc\n",
    result_text,
    flags=re.IGNORECASE |
    re.MULTILINE
)


try:

    encoded = result_text.encode(
        "cp932",
        errors="strict"
    )

except UnicodeEncodeError:

    encoded = result_text.encode(
        "cp932",
        errors="replace"
    )


with open(
    output_path,
    "wb"
) as f:

    f.write(encoded)


QtWidgets.QMessageBox.information(
    None,
    "DXF修正完了",
    "DXFの修正が完了しました。\n\n"
    + output_path
)
# ============================================================
# 未使用レイヤー削除
# ============================================================
# 空レイヤー削除
# ============================================================

print("")
print("============================================================")
print(" 空レイヤー削除")
print("============================================================")

# ------------------------------------------------------------
# 使用中レイヤーを取得
# ENTITIES + BLOCKS の全DXFから8コードを調査
# ------------------------------------------------------------

used_layers = set()

i = 0

while i < len(lines) - 1:

    if lines[i].strip() == "8":

        layer_name = lines[i + 1].strip()

        if layer_name:
            used_layers.add(layer_name)

    i += 2

print(
    "使用中レイヤー数:",
    len(used_layers)
)

# ------------------------------------------------------------
# LAYER TABLEを探す
# ------------------------------------------------------------

layer_table_start = None
layer_table_end = None

i = 0

while i < len(lines) - 1:

    if (
        lines[i].strip() == "0"
        and
        lines[i + 1].strip() == "TABLE"
    ):

        j = i + 2

        while j < len(lines) - 1:

            if (
                lines[j].strip() == "2"
                and
                lines[j + 1].strip() == "LAYER"
            ):

                layer_table_start = i

            if (
                lines[j].strip() == "0"
                and
                lines[j + 1].strip() == "ENDTAB"
            ):

                if layer_table_start is not None:

                    layer_table_end = j + 2

                break

            j += 1

        if layer_table_start is not None:
            break

    i += 1

# ------------------------------------------------------------
# LAYER TABLEが見つかった場合
# ------------------------------------------------------------

removed_layers = []

if (
    layer_table_start is not None
    and
    layer_table_end is not None
):

    table = lines[
        layer_table_start:
        layer_table_end
    ]

    # LAYERレコードを探す
    ranges = []

    i = 0

    while i < len(table) - 1:

        if (
            table[i].strip() == "0"
            and
            table[i + 1].strip() == "LAYER"
        ):

            start = i
            j = i + 2

            while j < len(table) - 1:

                if table[j].strip() == "0":
                    break

                j += 1

            # レイヤー名 2
            name = ""

            k = start

            while k < j - 1:

                if table[k].strip() == "2":

                    name = table[k + 1].strip()
                    break

                k += 2

            # ------------------------------------------------
            # 0レイヤーは絶対残す
            # 使用中レイヤーも残す
            # ------------------------------------------------

            if (
                name
                and
                name != "0"
                and
                name not in used_layers
            ):

                ranges.append(
                    (
                        start,
                        j
                    )
                )

                removed_layers.append(name)

            i = j
            continue

        i += 1

    # --------------------------------------------------------
    # 後ろから削除
    # --------------------------------------------------------

    for start, end in sorted(
        ranges,
        reverse=True
    ):

        del table[start:end]

    # --------------------------------------------------------
    # TABLEを戻す
    # --------------------------------------------------------

    lines[
        layer_table_start:
        layer_table_end
    ] = table

print(
    "空レイヤー削除:",
    len(removed_layers)
)

for name in removed_layers:

    print(
        "削除:",
        name
    )

else:

    print(
        "LAYER TABLEが見つかりません"
    )
#
# ★今回は完全にスキップ
#
# LAYER TABLEを直接変更しない。
# DXF構造破壊を防ぐため。
# ============================================================

print("")

print("============================================================")

print(" 未使用レイヤー削除")

print("============================================================")

print("今回はスキップします")

print("LAYER TABLEは変更しません")
