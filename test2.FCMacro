import FreeCAD as App
import FreeCADGui as Gui
import Part

# クリック位置を取得
sel = Gui.Selection.getSelectionEx()

if not sel:
    print("何も選択されていません")
else:
    # クリックした点（3D座標）
    p = sel[0].PickedPoints[0]

    # 三角形のサイズ（1 mm）
    s = 1.0
    s2 = 0.5
    # 三角形の3点を作成（クリック位置を基準にオフセット）
    p1 = p
    p2 = App.Vector(p.x + s, p.y, p.z)
    p3 = App.Vector(p.x, p.y + s2, p.z)

    # 三角形のワイヤーを作成
    edge1 = Part.makeLine(p1, p2)
    edge2 = Part.makeLine(p2, p3)
    edge3 = Part.makeLine(p3, p1)
    wire = Part.Wire([edge1, edge2, edge3])

    # FreeCAD ドキュメントに追加
    obj = App.ActiveDocument.addObject("Part::Feature", "R寸法")
    obj.Shape = wire

    App.ActiveDocument.recompute()

    print("三角形を作成しました:", p)
