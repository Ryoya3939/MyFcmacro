import FreeCAD as App
import FreeCADGui as Gui
import Part

sel = Gui.Selection.getSelectionEx()

if not sel:
    print("選択してください")
else:
    edge = sel[0].SubObjects[0]
    curve = edge.Curve

    print("Curve type:", type(curve))

    if isinstance(curve, Part.Circle):
        print("半径:", curve.Radius)
    elif isinstance(curve, Part.Line):
        print("直線です")
    else:
        print("その他の曲線です")
